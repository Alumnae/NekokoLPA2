-- Test input only. Constructs that the shipped SGP.22 / PKIX modules happen
-- not to use, so that support for them is not quietly lost.

Constructs DEFINITIONS EXPLICIT TAGS ::= BEGIN

Colour ::= ENUMERATED { red (0), green (1), blue (2) }

Flags ::= BIT STRING { alpha (0), beta (3), gamma (17) }

Coordinates ::= SET {
    x              [0] INTEGER,
    y              [1] INTEGER
}

Names ::= SET OF PrintableString

Extensible ::= SEQUENCE {
    required       INTEGER,
    optional       BOOLEAN DEFAULT TRUE,
    ...
}

Stamped ::= SEQUENCE {
    createdAt      UTCTime,
    expiresAt      GeneralizedTime,
    note           BMPString OPTIONAL
}

Nested ::= SEQUENCE {
    inner          SEQUENCE {
        list           SEQUENCE OF SEQUENCE {
            id             INTEGER,
            label          UTF8String
        },
        pick           CHOICE {
            one            [0] INTEGER,
            two            [1] OCTET STRING
        }
    }
}

Recursive ::= SEQUENCE {
    value          INTEGER,
    next           Recursive OPTIONAL
}

END
